package BusinessGoals {
    // Бизнес-цели Заказчика (пользователя, которому нужен доступ к ИИ-сервисам)
    requirement <BG> 'Бизнес-цели Murik DNS' {
        requirement <BG1> 'БЦ-1 Доступ в одно нажатие' {
            doc /* Открывать ChatGPT и Claude без ручной настройки DNS:
             * одно нажатие кнопки вместо правки свойств адаптера. */
        }
        requirement <BG2> 'БЦ-2 Лучший DNS для текущей сети' {
            doc /* Выбирать DNS по измерениям задержки в текущей сети,
             * а не по чужим советам и спискам из Интернета. */
        }
        requirement <BG3> 'БЦ-3 Безопасный откат' {
            doc /* Всегда возвращать исходные DNS, DoH и IPv6
             * одной кнопкой, даже после сбоя или смены адаптера. */
        }
        requirement <BG4> 'БЦ-4 Работа без внимания пользователя' {
            doc /* Запускаться с Windows, работать в трее
             * и восстанавливать подключение после смены сети. */
        }
        requirement <BG5> 'БЦ-5 Передача другу без установки' {
            doc /* Распространять папку программы архивом,
             * без установщика и без личных настроек автора. */
        }
    }
}
